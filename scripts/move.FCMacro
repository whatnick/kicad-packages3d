import FreeCAD, FreeCADGui, Draft
import Idf
import ImportGui

import re
import sys, os , argparse
import __builtin__

from step2wrl import *
    
FreeCAD.Console.PrintMessage("Importing: " + getStepFile() + "\n")

#Gui.activateWorkbench("PartWorkbench")
#Gui.SendMsgToActiveView("ViewFit")
Gui.activeDocument().activeView().viewTop()

oselection = Gui.Selection.getSelection()
bb=App.ActiveDocument.ActiveObject.Shape.BoundBox

"""
Move the step file by the given amount(s)
"""

#extract other arguments
for i in sys.argv[2:]:
    arg = i.lower().split("=")
    
    if len(arg) == 2:
        try:
            a = str(arg[0])
            d = float(arg[1])
            
            if a == "x":
                moveAll(d,0,0)
            if a == "y":
                moveAll(0,d,0)
            if a == "z":
                moveAll(0,0,d)
            
        except:
            pass
            
saveStepAndClose()
