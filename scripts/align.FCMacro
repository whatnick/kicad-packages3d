import FreeCAD, FreeCADGui, Draft
import Idf
import ImportGui

import re
import sys, os , argparse
import __builtin__

from step2wrl import *
    
FreeCAD.Console.PrintMessage("Importing: " + getStepFile() + "\n")

#Gui.activateWorkbench("PartWorkbench")
#Gui.SendMsgToActiveView("ViewFit")
Gui.activeDocument().activeView().viewTop()

oselection = Gui.Selection.getSelection()
bb=App.ActiveDocument.ActiveObject.Shape.BoundBox

"""
Given a STEP file, align sides to origin
"""

#extract other arguments
for i in sys.argv[2:]:
    i = i.lower()
    
    if i == "x-":
        alignXLeft()
    if i == "x+":
        alignXRight()
    if i == "y-":
        alignYBottom()
    if i == "y+":
        alignYTop()
    if i == "z-":
        alignZBottom()
    if i == "z+":
        alignZTop()
        
saveStepAndClose()
