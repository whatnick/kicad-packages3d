import FreeCAD, FreeCADGui, Draft
import Idf
import ImportGui

import re
import sys, os , argparse
import __builtin__

from step2wrl import *
    
FreeCAD.Console.PrintMessage("Importing: " + getStepFile() + "\n")

#Gui.activateWorkbench("PartWorkbench")
#Gui.SendMsgToActiveView("ViewFit")
Gui.activeDocument().activeView().viewTop()

oselection = Gui.Selection.getSelection()
bb=App.ActiveDocument.ActiveObject.Shape.BoundBox

#extract other arguments
for i in sys.argv[2:]:
    if i.lower() == "x":
        rotate_x()
    if i.lower() == "y":
        rotate_y()
    if i.lower() == "z":
        rotate_z()

if "tmp" not in sys.argv:
    out = getStepFile()        
    FreeCAD.Console.PrintMessage("Exporting: " + out + "\n")
    saveSTEP(out)
    exit()
    
else:
    out = getTempStepFile()
    FreeCAD.Console.PrintMessage("Exporting: " + out + "\n")
    saveSTEP(out)
